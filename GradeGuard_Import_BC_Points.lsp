; GradeGuard 9.3.1 - validated point import, no inferred line connectivity.
; Accepts headerless P,N,E,Z,D or GradeGuard Confidence Summary CSV.
; Quoted commas and escaped quotes are supported. Malformed/multiline rows,
; blank or zero elevations, and RED/unknown status rows are skipped.
; 3D command aliases import points only: CSV row order is not topology.
(vl-load-com)

(defun gg931:csv (s / i n ch token fields quoted bad)
  (setq i 1 n (strlen s) token "" fields '() quoted nil bad nil)
  (while (<= i n)
    (setq ch (substr s i 1))
    (cond
      ((= ch "\"")
       (if (and quoted (< i n) (= (substr s (+ i 1) 1) "\""))
         (progn (setq token (strcat token "\"")) (setq i (+ i 1)))
         (if (or quoted (= token ""))
           (setq quoted (not quoted))
           (setq bad T))))
      ((and (= ch ",") (not quoted))
       (setq fields (cons token fields) token ""))
      (T (setq token (strcat token ch))))
    (setq i (+ i 1)))
  (if (or quoted bad) nil (reverse (cons token fields))))

(defun gg931:number (s / i ch dots digits ok)
  (setq s (vl-string-trim " \t\r\n" s) i 1 dots 0 digits 0 ok T)
  (while (<= i (strlen s))
    (setq ch (substr s i 1))
    (cond
      ((and (= i 1) (member ch '("+" "-"))))
      ((= ch ".") (setq dots (+ dots 1)))
      ((wcmatch ch "#") (setq digits (+ digits 1)))
      (T (setq ok nil)))
    (setq i (+ i 1)))
  (if (and ok (> digits 0) (<= dots 1)) (distof s 2) nil))

(defun gg931:layer (name color)
  (if (not (tblsearch "LAYER" name))
    (entmakex (list '(0 . "LAYER") '(100 . "AcDbSymbolTableRecord")
                   '(100 . "AcDbLayerTableRecord") (cons 2 name) '(70 . 0)
                   (cons 62 color) '(6 . "Continuous")))))

(defun gg931:import (/ *error* file fh row vals pn north east elev status layer pt desc count skipped)
  (defun *error* (msg)
    (if fh (close fh))
    (if msg (princ (strcat "\nGradeGuard import stopped: " msg)))
    (princ))
  (setq file (getfiled "Select GradeGuard field CSV or confidence summary" "" "csv" 0))
  (if file
    (progn
      (setq fh (open file "r") count 0 skipped 0)
      (if fh
        (progn
          (gg931:layer "GG_GREEN_READY" 3)
          (gg931:layer "GG_YELLOW_REVIEW" 2)
          (while (setq row (read-line fh))
            (setq vals (gg931:csv row))
            (cond
              ((and vals (= (strcase (car vals)) "POINT")))
              ((and vals (>= (length vals) 5)
                    (setq pn (gg931:number (nth 0 vals)))
                    (> pn 0) (= pn (fix pn))
                    (setq north (gg931:number (nth 1 vals)))
                    (setq east (gg931:number (nth 2 vals)))
                    (setq elev (gg931:number (nth 3 vals)))
                    (/= elev 0.0)
                    (setq status (if (= (length vals) 5) "GREEN" (strcase (nth 5 vals))))
                    (member status '("GREEN" "YELLOW")))
               (setq layer (if (= status "GREEN") "GG_GREEN_READY" "GG_YELLOW_REVIEW")
                     pt (list east north elev) desc (nth 4 vals))
               (entmakex (list '(0 . "POINT") (cons 8 layer) (cons 10 pt)))
               (entmakex (list '(0 . "TEXT") (cons 8 layer)
                              (cons 10 (list (+ east 1.0) (+ north 1.0) elev))
                              '(40 . 1.0) (cons 7 (getvar "TEXTSTYLE"))
                              (cons 1 (strcat (nth 0 vals) " " desc " EL " (rtos elev 2 3)))))
               (setq count (+ count 1)))
              (T (setq skipped (+ skipped 1)))))
          (close fh) (setq fh nil)
          (princ (strcat "\nGradeGuard: " (itoa count) " points imported; " (itoa skipped)
                         " unsafe or malformed rows skipped. No connecting lines were inferred.")))
        (princ "\nCould not open CSV."))))
  (princ))

(defun c:GGIMPORTV9 () (gg931:import))
(defun c:GGIMPORTBC () (gg931:import))
(defun c:GGIMPORTV93D ()
  (princ "\nAutomatic 3D joining disabled: row order does not identify connected curb runs.")
  (gg931:import))
(defun c:GGIMPORTBC3D () (c:GGIMPORTV93D))
(princ "\nGradeGuard 9.3.1 import loaded. Run GGIMPORTV9 or GGIMPORTBC. 3D aliases import points only.")
(princ)
